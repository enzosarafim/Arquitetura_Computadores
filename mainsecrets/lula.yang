module exemplo-rede {
  yang-version 1.1;
  namespace "urn:exemplo:rede";
  prefix ex;

  organization "Exemplo Corp";
  contact "suporte@exemplo.com";
  description "Módulo básico para configuração de interface de rede.";

  revision "2026-10-08" {
    description "Versão inicial.";
  }

  container rede {
    description "Configurações de rede do dispositivo.";

    list interface {
      key "nome";

      leaf nome {
        type string;
        description "Nome da interface (ex: eth0).";
      }

      leaf habilitada {
        type boolean;
        default true;
        description "Status da interface.";
      }

      leaf endereco-ip {
        type string;
        description "Endereço IP atribuído à interface.";
      }
    }
  }
}
